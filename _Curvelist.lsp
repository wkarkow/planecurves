; _CURVELIST.LSP - curve function loader

(defun C:ABDANK () (load "Abdank"))
(defun C:AIRY () (load "Airy"))
(defun C:ALAIN () (load "Alain"))
(defun C:ALYSOID () (load "Alysoid"))
(defun C:AMPERSAND () (load "Ampersand"))
(defun C:ANGULARACCEL () (load "AngularAccel"))
(defun C:ANTIPARALINK () (load "Antiparalink"))
(defun C:APOLLONIAN () (load "Apollonian"))
(defun C:ARBELOS () (load "Arbelos"))
(defun C:ARCHIMEDEAN () (load "Archimedean"))
(defun C:ARCSOFSAMOTHRACE () (load "Arcs of Samothrace"))
(defun C:ASTROID () (load "Astroid"))
(defun C:ATOMSPIRAL() (load "Atomspiral"))
(defun C:ATRIPHTALOID() (load "Atriphtaloid"))
(defun C:ATZEMA () (load "Atzema"))
(defun C:AVRAMI () (load "Avrami"))
(defun C:BALLISTIC () (load "Ballistic"))
(defun C:BASESLIDER () (load "Baseslider"))
(defun C:BEAN () (load "Bean"))
(defun C:BEETLE () (load "Beetle"))
(defun C:BERNOULLIQ () (load "BernoulliQ"))
(defun C:BESACE () (load "Besace"))
(defun C:BESSEL () (load "Bessel"))
(defun C:BICORN () (load "Bicorn"))
(defun C:BICUSPID () (load "Bicuspid"))
(defun C:BIFOLIATE () (load "Bifoliate"))
(defun C:BIFOLIUM () (load "Bifolium"))
(defun C:BOOTH () (load "Booth"))
(defun C:BOUNCE () (load "Bounce"))
(defun C:BOWCURVE () (load "BowCurve"))
(defun C:BOWDITCH () (load "Bowditch"))
(defun C:BOWTIE () (load "Bowtie"))
(defun C:BRAKE () (load "Brake"))
(defun C:BULLET () (load "Bullet"))
(defun C:BURNSIDE () (load "Burnside"))
(defun C:BUTTERFLY () (load "Butterfly"))
(defun C:CAPRICORNOID () (load "Capricornoid"))
(defun C:CARDIOID () (load "Cardioid"))
(defun C:CARTESIAN () (load "Cartesian"))
(defun C:CASSCURVE () (load "CassCurve"))
(defun C:CASSINIAN () (load "Cassinian"))
(defun C:CATALAN () (load "Catalan"))
(defun C:CATENARY () (load "Catenary"))
(defun C:CATEQUAL () (load "Catequal"))
(defun C:CATEVOLUTE () (load "Catevolute"))
(defun C:CATSINE () (load "Catsine"))
(defun C:CAYLEYOVAL () (load "CayleyOval"))
(defun C:CAYLEYSEXTIC () (load "CayleySextic"))
(defun C:CENTEREDTROCHOID () (load "CenteredTrochoid"))
(defun C:CEVASECTRIX () (load "Cevasectrix"))
(defun C:CHRYSANTHEMUM () (load "Chrysanthemum"))
(defun C:CIRCRADIALSEXTIC () (load "CircRadialSextic"))
(defun C:CISSOID () (load "Cissoid"))
(defun C:CLINOID () (load "Clinoid"))
(defun C:CLAIRAUT () (load "Clairaut"))
(defun C:CLOTHOID () (load "Clothoid"))
(defun C:COCHLEOID () (load "Cochleoid"))
(defun C:CONCHAL () (load "Conchal"))
(defun C:CONCHCIRCLE () (load "ConchCircle"))
(defun C:CONCHNICOMEDES () (load "ConchNicomedes"))
(defun C:CORNOID () (load "Cornoid"))
(defun C:COSECANT () (load "Cosecant"))
(defun C:COSHSPIRAL () (load "CoshSpiral"))
(defun C:COSINE () (load "Cosine"))
(defun C:COTANGENT () (load "Cotangent"))
(defun C:CRANIOID () (load "Cranioid"))
(defun C:CROSSCURVE () (load "Crosscurve"))
(defun C:CTROCHOID () (load "CTrochoid"))
(defun C:CUBICEGG () (load "CubicEgg"))
(defun C:CUBICPARABOLA () (load "CubicParabola"))
(defun C:CURVEDSTAR () (load "CurvedStar"))
(defun C:CYCLICHARMONIC () (load "Cyclicharmonic"))
(defun C:CYCLOID () (load "Cycloid"))
(defun C:DAHLIA () (load "Dahlia"))
(defun C:DELANGES () (load "Delanges"))
(defun C:DELAUNAY () (load "Delaunay"))
(defun C:DELTOID () (load "Deltoid"))
(defun C:DESLUZE () (load "DeSluze"))
(defun C:DEVILS () (load "Devils"))
(defun C:DIOCLES () (load "Diocles"))
(defun C:DIPOLE () (load "Dipole"))
(defun C:DIVERGPARAB () (load "Divergparab"))
(defun C:DOPPLERSPIRAL () (load "Dopplerspiral"))
(defun C:DOUBLEHEART () (load "DoubleHeart"))
(defun C:DOUBLEU () (load "DoubleU"))
(defun C:DRAWBRIDGE () (load "Drawbridge"))
(defun C:DUMBBELL () (load "Dumbbell"))
(defun C:DUPLICATRIX () (load "Duplicatrix"))
(defun C:DUPORCQ () (load "Duporcq"))
(defun C:DURERSHELL () (load "DurerShell"))
(defun C:EGGCURVE () (load "EggCurve"))
(defun C:EIGHTCURVE () (load "EightCurve"))
(defun C:EHRHART () (load "Ehrhart"))
(defun C:ELASTICCAT () (load "ElasticCat"))
(defun C:ELASTICCURVE () (load "ElasticCurve"))
(defun C:ELLIPSEEVOLUTE () (load "EllipseEvolute"))
(defun C:ELLIPSEGLISSETTE () (load "EllipseGlissette"))
(defun C:ENPEDAL () (load "ENPedal"))
(defun C:EPICYCLOID () (load "Epicycloid"))
(defun C:EPISPIRAL () (load "Epispiral"))
(defun C:EPITROCHOID () (load "Epitrochoid"))
(defun C:EPITROCHOIDEVOLUTE () (load "EpitrochoidEvolute"))
(defun C:ERYTHROCYTE () (load "Erythrocyte"))
(defun C:EXPONENTIAL () (load "Exponential"))
(defun C:FALLINGSAND () (load "FallingSand"))
(defun C:FERMAT () (load "Fermat"))
(defun C:FISH () (load "Fish"))
(defun C:FOCALCIRC () (load "FocalCirc"))
(defun C:FOLIOID () (load "Folioid"))
(defun C:FOLIUM () (load "Folium"))
(defun C:FREETH () (load "Freeth"))
(defun C:GALILEAN () (load "Galilean"))
(defun C:GARFIELD () (load "Garfield"))
(defun C:GAUSSIANWAVE () (load "GaussianWave"))
(defun C:GEAR () (load "Gear"))
(defun C:GENHYPERBOLA () (load "GenHyperbola"))
(defun C:GENPOLAR () (load "GenPolar"))
(defun C:GENTRIG () (load "Gentrig"))
(defun C:GIELIS () (load "Gielis"))
(defun C:GOMPERTZ () (load "Gompertz"))
(defun C:GOMPDIST () (load "GompDist"))
(defun C:GOMPMAKE () (load "GompMake"))
(defun C:GUDERMANNIAN () (load "Gudermannian"))
(defun C:HABENICHT () (load "Habenicht"))
(defun C:HARMFORCED () (load "Harmforced"))
(defun C:HARMONICSPIRAL () (load "Harmonicspiral"))
(defun C:HARMONOGRAPH () (load "Harmonograph"))
(defun C:HARMSEMI () (load "Harmsemi"))
(defun C:HARMSTRONG () (load "Harmstrong"))
(defun C:HEART () (load "Heart"))
(defun C:HIPPIAS () (load "Hippias"))
(defun C:HIPPOPEDE () (load "Hippopede"))
(defun C:HOERL () (load "Hoerl"))
(defun C:HOLDITCHELLIPSE () (load "HolditchEllipse"))
(defun C:HOLDITCHPARABOLA () (load "HolditchParabola"))
(defun C:HOSPITAL () (load "Hospital"))
(defun C:HOSPEVOLUTE () (load "Hospevolute"))
(defun C:HYDROGEN2P () (load "Hydrogen2p"))
(defun C:HOURGLASS () (load "Hourglass"))
(defun C:HUMBERTCUBIC () (load "HumbertCubic"))
(defun C:HYPERBOLA () (load "Hyperbola"))
(defun C:HYPERFUN () (load "Hyperfun"))
(defun C:HYPERSPIRAL () (load "Hyperspiral"))
(defun C:HYPOCYCLOID () (load "Hypocycloid"))
(defun C:HYPOTROCHOID () (load "Hypotrochoid"))
(defun C:HYPOTREVOLUTE () (load "Hypotrevolute"))
(defun C:IRRADIANCE () (load "Irradiance"))
(defun C:INVEVOLUTOIDCIRCLE () (load "Invevolutoidcircle"))
(defun C:INVOLUTECIRCLE () (load "Involutecircle"))
(defun C:JERABEK () (load "Jerabek"))
(defun C:JOUKOWSKI () (load "Joukowski"))
(defun C:KAMPYLE () (load "Kampyle"))
(defun C:KAPPA () (load "Kappa"))
(defun C:KERATOID () (load "Keratoid"))
(defun C:KIEPERT () (load "Kiepert"))
(defun C:KIEROID () (load "Kieroid"))
(defun C:KILROY () (load "Kilroy"))
(defun C:KLEIN () (load "Klein"))
(defun C:KNOT () (load "Knot"))
(defun C:KULP () (load "Kulp"))
(defun C:LAPLACELIMIT () (load "LaPlaceLimit"))
(defun C:LEMNISCATEBERNOULLI () (load "LemniscateBernoulli"))
(defun C:LIMACON () (load "Limacon"))
(defun C:LIMAEVOLUTE () (load "Limaevolute"))
(defun C:LINKS () (load "Links"))
(defun C:LINTEARIA () (load "Lintearia"))
(defun C:LITUUS () (load "Lituus"))
(defun C:LOGARITHM () (load "Logarithm"))
(defun C:LOGISTIC () (load "Logistic"))
(defun C:LOGSPIRAL () (load "Logspiral"))
(defun C:LORIGA () (load "Loriga"))
(defun C:MACLAURIN () (load "Maclaurin"))
(defun C:MALTESE () (load "Maltese"))
(defun C:MASCOT () (load "Mascot"))
(defun C:MEANDER () (load "Meander"))
(defun C:MICHAELIS () (load "Michaelis"))
(defun C:MIE () (load "Mie"))
(defun C:MIXEDCUBIC () (load "Mixedcubic"))
(defun C:MONOMOLECULAR () (load "Monomolecular"))
(defun C:NEPHROID () (load "Nephroid"))
(defun C:NEWTONTRIDENT () (load "Newtontrident"))
(defun C:NICKALLS () (load "Nickalls"))
(defun C:NIELSENSPIRAL () (load "Nielsenspiral"))
(defun C:NODALCURVE () (load "Nodalcurve"))
(defun C:OCHOA () (load "Ochoa"))
(defun C:OPHIURIDE () (load "Ophiuride"))
(defun C:OXYHB () (load "Oxyhb"))
(defun C:PARABOLA () (load "Parabola"))
(defun C:PARABGLISSETTE () (load "ParabGlissette"))
(defun C:PARAINVERSE() (load "Parainverse"))
(defun C:PARABINVOLUTE() (load "Parabinvolute"))
(defun C:PARACYCLOID() (load "Paracycloid"))
(defun C:PARANEGPEDAL() (load "Paranegpedal"))
(defun C:PARAPEDAL() (load "Parapedal"))
(defun C:PARASPIRAL() (load "Paraspiral"))
(defun C:PASCHEN() (load "Paschen"))
(defun C:PEARLSOFSLUZE() (load "PearlsofSluze"))
(defun C:PENDULUMENERGY() (load "PendulumEnergy"))
(defun C:PERIAPSIS() (load "Periapsis"))
(defun C:PERICYCLOID() (load "Pericycloid"))
(defun C:PIRIFORM() (load "Piriform"))
(defun C:PLANCK() (load "Planck"))
(defun C:PLATEAU() (load "Plateau"))
(defun C:POINSOT() (load "Poinsot"))
(defun C:POISSON() (load "Poisson"))
(defun C:POLYGASTEROID() (load "Polygasteroid"))
(defun C:POWERFUNC() (load "Powerfunc"))
(defun C:PROPELLER() (load "Propeller"))
(defun C:PURSUIT() (load "Pursuit"))
(defun C:QUARTEGG() (load "Quartegg"))
(defun C:QUATREFOIL() (load "Quatrefoil"))
(defun C:QUINTICHEART() (load "QuinticHeart"))
(defun C:QUINTICSERPENTINE() (load "QuinticSerpentine"))
(defun C:RAINDROP() (load "Raindrop"))
(defun C:RAMPHOID() (load "Ramphoid"))
(defun C:RATBICIRCULAR() (load "RatBicircular"))
(defun C:RATCIRCCUBIC() (load "RatCircCubic"))
(defun C:RECTHYPERBOLA() (load "RectHyperbola"))
(defun C:RECIPEXP() (load "RecipExp"))
(defun C:RECIPPOWEREXP() (load "RecipPowerExp"))
(defun C:RECTELLIPSE() (load "Rectellipse"))
(defun C:RIBAUCOUR() (load "Ribaucour"))
(defun C:ROSE() (load "Rose"))
(defun C:ROSILLO() (load "Rosillo"))
(defun C:SACRE() (load "Sacre"))
(defun C:SALMONQ() (load "SalmonQ"))
(defun C:SAWBLADE() (load "Sawblade"))
(defun C:SECANT() (load "Secant"))
(defun C:SECTRIXM() (load "SectrixM"))
(defun C:SEMICUBPARAB() (load "Semicubparab"))
(defun C:SERPENTINE() (load "Serpentine"))
(defun C:SINE () (load "Sine"))
(defun C:SINEANGTROCH () (load "SineAngTroch"))
(defun C:SINESUM () (load "SineSum"))
(defun C:SINETROCHOID () (load "SineTrochoid"))
(defun C:SINETROCHPHASE () (load "SineTrochPhase"))
(defun C:SINHSPIRAL () (load "SinhSpiral"))
(defun C:SINSPIRAL () (load "SinSpiral"))
(defun C:SINUSOIDALRADIUS () (load "SinusoidalRadius"))
(defun C:SPIRAL () (load "Spiral"))
(defun C:SPIRIC () (load "Spiric"))
(defun C:SPIRO3 () (load "SPIRO3"))
(defun C:SQUIRCLE () (load "SQUIRCLE"))
(defun C:STIRLING() (load "Stirling"))
(defun C:STIRRUP() (load "Stirrup"))
(defun C:STROPHOID() (load "Strophoid"))
(defun C:STURMSPIRAL() (load "SturmSpiral"))
(defun C:SUPERELLIPSE() (load "Superellipse"))
(defun C:SUPERROSE() (load "Superrose"))
(defun C:SUPERSPIRAL() (load "SuperSpiral"))
(defun C:SWASTIKA() (load "Swastika"))
(defun C:SWIMMINGDOG() (load "SwimmingDog"))
(defun C:SYNTRACTRIX() (load "Syntractrix"))
(defun C:SYNTREPENT() (load "Syntrepent"))
(defun C:TANGENT() (load "Tangent"))
(defun C:TANHC() (load "Tanhc"))
(defun C:TANHSPIRAL() (load "TanhSpiral"))
(defun C:TEARDROP() (load "Teardrop"))
(defun C:TETRACHORIC() (load "Tetrachoric"))
(defun C:TIGHTROPE() (load "Tightrope"))
(defun C:TRACTCIRC() (load "TractCirc"))
(defun C:TRACTRIX() (load "Tractrix"))
(defun C:TRACTRIXSPIRAL() (load "TractrixSpiral"))
(defun C:TRIDENTDESCARTES() (load "TridentDescartes"))
(defun C:TRIFOLIUM() (load "Trifolium"))
(defun C:TRIG() (load "Trig"))
(defun C:TROCHOID() (load "Trochoid"))
(defun C:TROPOSKEIN() (load "Troposkein"))
(defun C:TROTT() (load "Trott"))
(defun C:TSCHIRNHAUS() (load "Tschirnhaus"))
(defun C:TUKEY() (load "Tukey"))
(defun C:UEKI() (load "Ueki"))
(defun C:Wagner() (load "Wagner"))
(defun C:WATTS() (load "Watts"))
(defun C:WEIBULL() (load "Weibull"))
(defun C:WHIRL () (load "Whirl"))
(defun C:WITCH () (load "Witch"))
(defun C:YINYANG() (load "YinYang"))
(defun C:ZAHRADNIK() (load "Zahradnik"))
(defun C:CURVELOAD() (load "_Curve"))
